# Requirements test document with image
Test document for ReqIF editor

# Specification: Specification1

## REQ_1
Introduction
- Type: Heading
- Platform: Windows, Linux, MacOS
- State: Draft
- Comment: Initial revision

### REQ_2
This document serves as a test input for the ReqIF-editor.
- Type: Information
- Platform: Windows, Linux, MacOS
- State: Draft
- Comment: This comment uses paragraphs as newlines.
  Here is a second line2.
  [04.04.2026, meow] bla

### REQ_10: REQ_13
A typical use case might look like this:
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- Type: Requirement
- Platform: Windows, Linux, MacOS
- State: Draft
- Comment:
  1. Initial revision
  2. Added ordered list
  3. Third line

### REQ_3
The application must work on the windows operating system.
- Type: Requirement
- Platform: Windows
- State: Draft
- Comment: Line 1 with div
  Line 2 with div
  Line 3 with div

### REQ_4
The application must work on the linux operating system.
- Type: Requirement
- Platform: Linux
- State: Draft
- Comment: Initial revision

### REQ_5
The application must work on the MAC OS operating system.
- Type: Requirement
- Platform: MacOS
- State: Draft
- Comment: Initial revision

## REQ_6
Functionality
- Type: Heading
- Platform: Windows, Linux, MacOS
- State: Draft
- Comment: Initial revision

### REQ_11
Import and export
- Type: Heading
- Platform: Windows, Linux, MacOS
- State: Draft
- Comment: Initial revision

#### REQ_7
The program must be able to load files conforming to ReqIf version 1.0.
- Type: Requirement
- Platform: Windows, Linux, MacOS
- State: Draft
- Comment: Initial revision

#### REQ_8
The program must be able to save files conforming to ReqIf version 1.0.
Some characters may need to be escaped: [brackets] Some non ascii characters: äö
This text should be indented.
- Type: Requirement
- Platform: Windows, Linux, MacOS
- State: Draft
- Comment: Initial revision

#### REQ_9
A round trip testing strikethrough consisting of loading a file and saving it must produce equivalent output. Only these fields shall be modified:
- LAST-CHANGE
- COMMENT
- SOURCE-TOOL-ID
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
- COMMENT
There is more text after the long list. Lorem Ipsum dolor sit amet.
- Type: Requirement
- Platform: Windows, Linux, MacOS
- State: Draft
- Comment: Initial revision

### REQ_12
Edit
- Type: Heading
- Platform: Windows, Linux, MacOS
- State: Draft
- Comment: Initial revision

#### REQ_10
Only contents in columns marked as editable can be modified initially when a new document is imported.
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
dummy line
This is a caption for the table that follows.
| Column 1 | Column 2 | 3 | More columns | this is a very long table header |
| --- | --- | --- | --- | --- |
| text in cell 1 | text in cell 2 | 3 | text in cell 4 | text in cell 5 |
| text in cell 6 | text in cell 7 | 8 | text in cell 9 | text in cell 10 |
- Type: Requirement
- Platform: Windows, Linux, MacOS
- State: Draft
