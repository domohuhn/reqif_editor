# Requirements test document
Test document for ReqIF editor

# Specification: Specification1

## R1: REQ_1
Introduction
- Type: Heading
- Platform: Windows, Linux, MacOS
- State: Draft
- Test Integer: 42
- Test REAL: 43.0
- Test DATE: 2023-11-22T11:42:13+01:00
- Test bool: true
- Comment: Initial revision

### R2: REQ_2
This document serves as a test input for the ReqIF-editor.
- Type: Information
- Platform: Windows, Linux, MacOS
- Comment: Initial revision

### R3: REQ_3
The application must work on the windows operating system.
- Type: Requirement
- Platform: Windows
- State: Draft
- Comment: Initial revision

### R4: REQ_4
The application must work on the linux operating system.
- Type: Requirement
- Platform: Linux
- State: Draft
- Comment: Initial revision

### R5: REQ_5
The application must work on the MAC OS operating system.
- Type: Requirement
- Platform: MacOS
- State: Draft
- Comment: Initial revision

## R6: REQ_6
Functionality
- Type: Heading
- Platform: Windows, Linux, MacOS
- State: Draft
- Comment: Initial revision

### R11: REQ_11
Import and export
- Type: Heading
- Platform: Windows, Linux, MacOS
- State: Draft
- Comment: Initial revision

#### R7: REQ_7 <tag>
The program must be able to load files conforming to ReqIf version 1.0.
- Object ID: REQ_7
- Type: Requirement
- Platform: Windows, Linux, MacOS
- State: Draft
- Comment: Initial revision

#### R8: REQ_8
The program must be able to save files conforming to ReqIf version 1.0.
Some characters may need to be escaped: [brackets] Some non ascii characters: äö
- Type: Requirement
- Platform: Windows, Linux, MacOS
- State: Draft
- Comment: Initial revision

#### R9: REQ_9
A round trip testing strikethrough consisting of loading a file and saving it must produce equivalent output. Only these fields shall be modified:
- LAST-CHANGE
- COMMENT
- SOURCE-TOOL-ID
- Type: Requirement
- Platform: Windows, Linux, MacOS
- State: Draft
- Comment: Initial revision

### R12: REQ_12
Edit
- Type: Heading
- Platform: Windows, Linux, MacOS
- State: Draft
- Comment: Initial revision

#### R10: REQ_10
Only contents in columns marked as editable can be modified.
- Type: Requirement
- Platform: Windows, Linux, MacOS
- State: Draft
- Comment: Initial revision <tag>
